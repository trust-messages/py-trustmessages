Messages DEFINITIONS ::= BEGIN

Message ::= CHOICE {
  data-request      DataRequest,
  data-response     DataResponse,
  format-request    FormatRequest,
  format-response   FormatResponse,
  fault             Fault
}

FormatRequest ::= [APPLICATION 0] IMPLICIT NULL

FormatResponse ::= [APPLICATION 1] IMPLICIT SEQUENCE {
  format      Format,
  assessment  PrintableString,
  trust       PrintableString
}

DataRequest ::= [APPLICATION 2] IMPLICIT SEQUENCE {
  rid   INTEGER,
  type  ENUMERATED { trust (0), assessment (1) },
  query Query
}

DataResponse ::= [APPLICATION 3] IMPLICIT SEQUENCE {
  provider  Entity,
  format    Format,
  type      ENUMERATED { trust (0), assessment (1) },
  rid       INTEGER,
  response  SEQUENCE OF Rating
}

Rating ::= [APPLICATION 4] IMPLICIT SEQUENCE {
  source  Entity,
  target  Entity,
  service Service,
  date    BinaryTime,
  value   ANY
}

Query ::= CHOICE {
  cmp Comparison,
  log Logical
}

Comparison ::= [APPLICATION 5] IMPLICIT SEQUENCE {
    op    ENUMERATED { eq (0), ne (1), lt (2), le (3), gt (4), ge (5) },
    value Value
}

Logical ::= [APPLICATION 6] IMPLICIT SEQUENCE {
  op  ENUMERATED { and (0), or (1) },
  l   Query,
  r   Query
}

Value ::= CHOICE {
  source  [APPLICATION 0] IMPLICIT Entity,
  target  [APPLICATION 1] IMPLICIT Entity,
  date    [APPLICATION 2] IMPLICIT BinaryTime,
  service [APPLICATION 3] IMPLICIT Service
}

Fault ::= [APPLICATION 7] IMPLICIT SEQUENCE {
  value   ENUMERATED { invalid-parameters (0), internal-error (1) },
  message PrintableString
}

Format ::= OBJECT IDENTIFIER

Entity ::= PrintableString

Service ::= PrintableString

BinaryTime ::= INTEGER

END
